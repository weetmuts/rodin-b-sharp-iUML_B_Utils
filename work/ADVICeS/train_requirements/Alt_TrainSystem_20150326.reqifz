# Specification: Specification Document
- Description: Requirements Document

## R8 (Headline)
Safety Conditions

### SAF-1 (Informal Requirement)
A block should be reserved for at most one route.
- RequirementRole: Requirement

### SAF-2 (Informal Requirement)
The signal of a route should only be set to green when all blocks of the route are reserved for it, and are unoccupied, and when all points of this route are properly positioned.
- RequirementRole: Requirement

### SAF-3 (Informal Requirement)
A point should only be re-positioned if it belongs to a block which is in a reserved, but not yet formed, route.
- RequirementRole: Requirement

### SAF-4 (Informal Requirement)
No blocks of a reserved, but not yet formed, route should be occupied.
- RequirementRole: Requirement

## R9 (Headline)
Moving Conditions

### MVT-1 (Informal Requirement)
Once a block of a formed route becomes unoccupied it is freed (atomically??)
- RequirementRole: Requirement

### MVT-2 (Informal Requirement)
Having been formed, a route remains so, while there are reserved blocks in it.
- RequirementRole: Requirement

### MVT-3 (Informal Requirement)
A formed route should be freed when no blocks are reserved for it. This implies that the route is no longer formed, nor reserved.
- RequirementRole: Requirement

## R13 (Headline)
Train Assumptions

### TRN-1 (Informal Requirement)
A train cannot split while in the network
- RequirementRole: Assumption

### TRN-2 (Informal Requirement)
A train cannot move backwards in the network
- RequirementRole: Assumption

### TRN-3 (Informal Requirement)
A train cannot enter in the middle of a route. It has to do so through its first block.
- RequirementRole: Assumption

### TRN-4 (Informal Requirement)
A train cannot leave a route without first occupying then freeing all its blocks
- RequirementRole: Assumption

## R17 (Headline)
Failure Assumptions

### FLR-1 (Informal Requirement)
Trains are equipped with the Automatic Train Protection system, which guarantees that they cannot enter a route guarded by a red signal
- RequirementRole: Assumption

### FLR-2 (Informal Requirement)
Trains are equipped with special bindings, which guarantee that they cannot be mechanically broken.
- RequirementRole: Assumption

### FLR-3 (Informal Requirement)
The Automatic Protection System and a slight delay observed by the track circuit guarantee that a train moving backward cannot occupy again a block which has been physically freed.
- RequirementRole: Assumption

### FLR-4 (Informal Requirement)
A block occupancy detection (track circuit) fault should be handled in a fail-safe way.
- RequirementRole: Requirement

### FLR-5 (Informal Requirement)
The case where a train derails and leaves its block(s) is not treated here
- RequirementRole: Assumption

## R23 (Headline)
Functional Requirements

### FUN-1 (Informal Requirement)
The goal of the train system is to safely control trains moving on a track network (meaning???)
- RequirementRole: Assumption

### FUN-2 (Informal Requirement)
A route can be reserved for a train. The software is in charge of controlling the reservation process
- RequirementRole: Requirement

### FUN-3 (Informal Requirement)
A block can be reserved or free
- RequirementRole: Requirement

### FUN-4 (Informal Requirement)
An occupied block is always reserved
- RequirementRole: Requirement

### FUN-5 (Informal Requirement)
A route is made of two or more (??) blocks. The route should only be reserved when all of its blocks have been reserved.
- RequirementRole: Requirement

### FUN-6 (Informal Requirement)
A reserved route should be formed by positioning its points
- RequirementRole: Requirement

### FUN-7 (Informal Requirement)
A formed route is always a reserved route
- RequirementRole: Requirement

### FUN-8 (Informal Requirement)
Once it is formed, a route is made available for the incoming train by turning its signal to green
- RequirementRole: Requirement

## R24 (Headline)
Environment Assumptions

### ENV-1 (Informal Requirement)
A track network may contain some special components: points and crossings
- RequirementRole: Assumption

### ENV-2 (Informal Requirement)
A point should have two positions: left or right
- RequirementRole: Assumption

### ENV-3 (Informal Requirement)
A track network is made of a number of fixed blocks
- RequirementRole: Assumption

### ENV-4 (Informal Requirement)
A special component (points or crossings) is always attached to a given block. And a block contains at most one special component
- RequirementRole: Assumption

### ENV-5 (Informal Requirement)
A block may be occupied or unoccupied by a train
- RequirementRole: Assumption

### ENV-6 (Informal Requirement)
A network has a fixed number of routes. Each route is characterized by a sequence of adjacent blocks
- RequirementRole: Assumption

### ENV-7 (Informal Requirement)
A route is also characterized by the positions of the points which are situated in blocks composing it
- RequirementRole: Assumption

### ENV-8 (Informal Requirement)
The first block of a route cannot be part of another route unless it is also the first or last block of that route
- RequirementRole: Assumption

### ENV-9 (Informal Requirement)
The last block of a route cannot be part of another route unless it is also the first or last block of that route
- RequirementRole: Assumption

### ENV-10 (Informal Requirement)
A route connects its first block to its last one in a continuous manner
- RequirementRole: Assumption

### ENV-11 (Informal Requirement)
A route contains no cycles
- RequirementRole: Assumption

### ENV-12 (Informal Requirement)
Each route is protected by a signal situated just before its first block
- RequirementRole: Assumption

### ENV-13 (Informal Requirement)
A signal can be red or green. Trains are supposed to stop at red signals
- RequirementRole: Assumption

### ENV-14 (Informal Requirement)
Routes having the same first block share the same signal
- RequirementRole: Assumption

### ENV-15 (Informal Requirement)
A green signal turns back to red automatically as soon as the first block is made occupied
- RequirementRole: Assumption

# Specification
- Description: Glossary

## phenomena (Informal Phenomena)
- Synonyms: phenomenon, designation

## R3

## FUN-1 (Informal Requirement)
The goal of the train system is to safely control trains moving on a track network

## FUN-2 (Informal Requirement)
A route can be reserved for a train. The software is in charge of controlling the reservation process

## FUN-3 (Informal Requirement)
A block can be reserved or free

## FUN-4 (Informal Requirement)
An occupied block is always reserved

## FUN-5 (Informal Requirement)
Reserving a route consists in reserving the individual blocks it is made of. Once this is done, the route is said to be reserved

## FUN-6 (Informal Requirement)
Once it is reserved, a route has to be formed by properly positioning its points

## FUN-7 (Informal Requirement)
A formed route is always a reserved route

## FUN-8 (Informal Requirement)
Once it is formed, a route is made available for the incoming train by turning its signal to green

## R45 (Informal Requirement)
